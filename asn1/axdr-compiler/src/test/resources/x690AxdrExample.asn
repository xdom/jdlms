X690_AXDR_EXAMPLE DEFINITIONS::=
BEGIN

PersonnelRecord ::= [APPLICATION 0] IMPLICIT SEQUENCE {
	name Name,
	title [0] VisibleString OPTIONAL,
	number EmployeeNumber,
	dateOfHire [1] Date,
	nameOfSpouse [2] Name,
	children [3] IMPLICIT SEQUENCE OF ChildInformation,
	stillEmployed BOOLEAN DEFAULT true
}

ChildInformation ::= SEQUENCE {
	name Name,
	dateOfBirth [0] Date,
	gender Gender
}

Gender ::= ENUMERATED 
{
	male(1), 
	female(2)
}

Name ::= [APPLICATION 1] IMPLICIT SEQUENCE {
	givenName VisibleString,
	initial VisibleString,
	familyName VisibleString
}

EmployeeNumber ::= [APPLICATION 2] IMPLICIT INTEGER
Date ::= [APPLICATION 3] IMPLICIT VisibleString -- YYYYMMDD

END
